// Generated by `mongoose architecture generate`. Do not edit by hand.
package MongooseAgents {
  part def MongooseRuntime;
  part def Agent;
  part def Capability;
  part runtime : MongooseRuntime;

  part njord : Agent {
    attribute commandName = "Njord";
    attribute displayName = "Njord";
    attribute manifestPath = "agents/njord/agent.json";
    attribute entrypointPath = "agents/njord/agent.py";
    attribute llmMode = "optional";
    attribute taskType = "budget";
    attribute taskType = "finance";
    attribute taskType = "ynab";
    attribute requiredConfiguration = "YNAB_ACCESS_TOKEN";
    attribute requiredConfiguration = "YNAB_BUDGET_ID";
    part njord_brief : Capability {
      attribute name = "brief";
      attribute displayName = "Manual Financial Brief";
      attribute entrypointPath = "agents/njord/agent.py";
      attribute llmMode = "optional";
      attribute taskType = "brief";
      attribute taskType = "finance";
      attribute taskType = "financial-brief";
      attribute taskType = "weekly-brief";
      attribute taskType = "ynab";
      attribute requiredConfiguration = "YNAB_ACCESS_TOKEN";
      attribute requiredConfiguration = "YNAB_BUDGET_ID";
    }
    part njord_config_status : Capability {
      attribute name = "config-status";
      attribute displayName = "Configuration Status";
      attribute entrypointPath = "agents/njord/agent.py";
      attribute llmMode = "none";
      attribute taskType = "configuration";
      attribute taskType = "credential-status";
      attribute taskType = "setup";
    }
    part njord_finance_review : Capability {
      attribute name = "finance-review";
      attribute displayName = "Finance Review";
      attribute entrypointPath = "agents/njord/agent.py";
      attribute llmMode = "optional";
      attribute taskType = "cash-flow-forecast";
      attribute taskType = "finance";
      attribute taskType = "finance-review";
      attribute taskType = "financial-risk";
      attribute taskType = "review";
      attribute taskType = "ynab";
      attribute requiredConfiguration = "YNAB_ACCESS_TOKEN";
      attribute requiredConfiguration = "YNAB_BUDGET_ID";
    }
    part njord_hello_world : Capability {
      attribute name = "hello-world";
      attribute displayName = "Hello World";
      attribute entrypointPath = "agents/njord/agent.py";
      attribute llmMode = "none";
      attribute taskType = "connection-test";
      attribute taskType = "diagnostic";
    }
    part njord_ynab_budget_summary : Capability {
      attribute name = "ynab-budget-summary";
      attribute displayName = "YNAB Budget Summary";
      attribute entrypointPath = "agents/njord/agent.py";
      attribute llmMode = "optional";
      attribute taskType = "budget-summary";
      attribute taskType = "finance";
      attribute taskType = "review-needed";
      attribute taskType = "ynab";
      attribute requiredConfiguration = "YNAB_ACCESS_TOKEN";
      attribute requiredConfiguration = "YNAB_BUDGET_ID";
    }
    part njord_ynab_spending_review : Capability {
      attribute name = "ynab-spending-review";
      attribute displayName = "YNAB Spending Review";
      attribute entrypointPath = "agents/njord/agent.py";
      attribute llmMode = "optional";
      attribute taskType = "cash-flow";
      attribute taskType = "finance";
      attribute taskType = "spending-review";
      attribute taskType = "transactions";
      attribute taskType = "ynab";
      attribute requiredConfiguration = "YNAB_ACCESS_TOKEN";
      attribute requiredConfiguration = "YNAB_BUDGET_ID";
    }
  }
  connect runtime to njord;

}
